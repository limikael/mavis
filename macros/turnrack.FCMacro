#
# Might be a better way: https://forum.freecadweb.org/viewtopic.php?t=4137
#

from freecad.gears.features import ViewProviderGear, involute_gear, involute_gear_rack
import math

TEETH_DISTANCE=5
THICKNESS=10
BETA_START=0
BETA_END=-11.25
NUMBER_OF_TEETH=27
HEIGHT=10

def makeRackPart():
	o=App.ActiveDocument.addObject("Part::FeaturePython", "InvoluteRack")
	involute_gear_rack(o)
	ViewProviderGear(o.ViewObject)

	o.thickness=THICKNESS
	o.teeth=1
	o.module=TEETH_DISTANCE/math.pi
	o.height=HEIGHT

	return o

parts=[]
y=0

for i in range(0,NUMBER_OF_TEETH):
	beta=BETA_START+i*(BETA_END-BETA_START)/NUMBER_OF_TEETH
	dist=TEETH_DISTANCE/math.cos(math.radians(beta))

	part=makeRackPart()
	part.beta=beta
	part.Placement.Base=FreeCAD.Vector(0,y,0)
	parts.append(part)

	y=y+dist

u=App.ActiveDocument.addObject("Part::MultiFuse","Union")
u.Shapes=parts
u.Label="Linear Beta Rack"

App.ActiveDocument.recompute()
Gui.SendMsgToActiveView("ViewFit")

print "Done..."
